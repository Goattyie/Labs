(defun c:build_object()
  (command "_osnap" "_off")
  (command "_-view" "_SWISO")
  (initget 1)
  (setq bp (getpoint "Введите базовую точку:"))
  (initget 7)
  (setq l (getreal "Введите длину фритюрницы (45):"))
  (initget 7)
  (setq w (getreal "Введите ширину фритюрницы (27):"))
  (initget 7)
  (setq h (getreal "Введите высоту фритюрницы (30):"))

  (princ "\nВведите высоту ножек фритюрницы  (3)")
  (princ (list "<=" (/ h 4)))
  (initget 7)
  (setq l_h (getreal))
  (while (> l_h (/ h 4))
    (princ "Высота ножек превышает допустимую высоту.\n Повторите ввод высоты ножек фритюрницы ")
    (princ (list "<=" (/ h 4)))
    (initget 7)
    (setq l_h (getreal))
    )
  
  (princ "\nВведите длину задней панели фритюрницы (12) ")
  (princ (list "<=" (/ l 2) "и >=" (/ l 8)))
  (initget 7)
  (setq p_l (getreal))
  (while (or (> p_l (/ l 2)) (< p_l (/ l 8)))
    (princ "Длина задней панели не входит в допустимый диапазон.\n Повторите ввод длины задней панели ")
    (princ (list "<=" (/ l 2) "и >=" (/ l 8)))
    (initget 7)
    (setq p_l (getreal))
    )

  (princ "\nВведите ширину задней панели фритюрницы (23) ")
  (princ (list "<=" w "и >=" (/ w 8)))
  (initget 7)
  (setq p_w (getreal))
  (while (or (> p_w w) (< p_w (/ w 8)))
    (princ "Ширина задней панели не входит в допустимый диапазон.\n Повторите ввод ширины задней панели ")
    (princ (list "<=" w "и >=" (/ w 8)))
    (initget 7)
    (setq p_w (getreal))
    )

  (princ "\nВведите высоту задней панели фритюрницы (14) ")
  (princ (list "<=" (/ h 1.2) "и >=" (/ h 5)))
  (initget 7)
  (setq p_h (getreal))
  (while (or (> p_h (/ h 1.2)) (< p_h (/ h 5)))
    (princ "Высота задней панели  не входит в допустимый диапазон.\n Повторите ввод высоты задней панели ")
    (princ (list "<=" (/ h 1.2) "и >=" (/ h 5)))
    (initget 7)
    (setq p_h (getreal))
    )

  (princ "\nВведите длину ручки сетки фритюрницы (24) ")
  (princ (list "<=" l "и >=" (/ l 8)))
  (initget 7)
  (setq h_l (getreal))
  (while (or (> h_l l) (< h_l (/ l 8)))
    (princ "Длина ручки сетки не входит в допустимый диапазон.\n Повторите ввод длины ручки сетки ")
    (princ (list "<=" l "и >=" (/ l 8)))
    (initget 7)
    (setq h_l (getreal))
    )

  (princ "\nВведите ширину ручки сетки фритюрницы (7) ")
  (princ (list "<=" (/ w 2) "и >=" (/ w 13.5)))
  (initget 7)
  (setq h_w (getreal))
  (while (or (> h_w (/ w 2)) (< h_w (/ w 13.5)))
    (princ "Ширина ручки сетки не входит в допустимый диапазон.\n Повторите ввод ширины ручки сетки ")
    (princ (list "<=" (/ w 2) "и >=" (/ w 13.5)))
    (initget 7)
    (setq h_w (getreal))
    )

  (princ "\nВведите радиус округления ручки сетки (3)")
  (princ (list "<=" (/ h_w 2)))
  (initget 7)
  (setq h_r (getreal))
  (while (> h_r (/ h_w 2))
    (princ "Радиус округления больше допустимого значения.\n Повторите ввод радиуса округления ручки ")
    (princ (list "<=" (/ h_w 2)))
    (initget 7)
    (setq h_r (getreal))
    )
  
  (princ "\nВведите радиус ручки от крышки фритюрницы (2.5)")
  (princ (list "<=" (/ l 6)))
  (initget 7)
  (setq lid_r (getreal))
  (while (> lid_r (/ l 6))
    (princ "Радиус ручки больше допустимого значения.\n Повторите ввод радиуса ручки ")
    (princ (list "<=" (/ l 6)))
    (initget 7)
    (setq lid_r (getreal))
    )

  (princ "\nВведите радиус таймера (2.5)")
  (princ (list "<=" (/ p_l 2) "и <=" (/ p_w 4)))
  (initget 7)
  (setq t_r (getreal))
  (while (or (> t_r (/ p_l 2)) (> t_r (/ p_w 4)))
    (princ "Радиус таймера не входит в допустимый диапазон.\n Повторите ввод радиуса таймера ")
    (princ (list "<=" (/ p_l 2) "и <=" (/ p_w 4)))
    (initget 7)
    (setq t_r (getreal))
    )
  
  (initget 7)
  (setq btn_n (getint "Введите количество кнопок (1-3):"))
  (while (> btn_n 3)
    (princ "Количество кнопок превышает допустимое значение.\n Повторите ввод количества кнопок (1-3)")
    (initget 7)
    (setq btn_n (getint))
    )
  
  (command "_box" (list (+ (car bp) (/ w 13.5)) (+ (cadr bp) (/ l 22.5)) (caddr bp)) "_l" (/ w 9) (/ l 15) l_h )
  (setq legs (entlast))
  (command "_copy" legs "" (list (car bp) (cadr bp) (caddr bp)) (list (+ (car bp) (- w  (/ w 6.75) (/ w 9))) (cadr bp) (caddr bp)))
  (command "_union" legs (entlast) "")
  (command "_copy" legs "" (list (car bp) (cadr bp) (caddr bp)) (list (car bp) (+ (cadr bp) (- l (/ l 11.25) (/ l 15))) (caddr bp)))
  (command "_union" legs (entlast) "")

  (command "_box" (list (car bp) (cadr bp) (+ (caddr bp) l_h)) "_l" w l (- h l_h))
  (setq main (entlast))
  (command "_-view" "_SWISO")
  (command "_union" main legs "")
  
  (command "_cylinder" (list (+ (car bp) (/ w 2)) (+ (cadr bp) (/ l 2)) (+ (caddr bp) h)) lid_r (/ w 18)"")
  (setq lid_handler (entlast))
  (command "_cylinder" (list (+ (car bp) (/ w 2)) (+ (cadr bp) (/ l 2)) (+ (caddr bp) h)) (/ lid_r 1.25) (/ w 18)"")
  (command "_subtract" lid_handler "" (entlast) "")
  (command "_rotate3d" lid_handler "" "Y" (list (+ (car bp) (/ w 2)) (+ (cadr bp) (/ l 2)) (+ (caddr bp) h)) 90)
  (command "_move" (entlast) "" bp (list (- (car bp) (/ w 36)) (cadr bp) (caddr bp)))
  (command "_union" main lid_handler "")
  
  (command "_box" bp "_l" p_w p_l p_h)
  (command "_move" (entlast) "" (list (+ (car bp) (/ p_w 2)) (cadr bp) (caddr bp)) (list (+ (car bp) (/ w 2)) (+ (cadr bp) l) (+ (caddr bp) (/ h 1.25))))
  (command "_union" main (entlast)"")

  (setq x_pos (+ (/ (- w p_w) 2) (/ p_w 4)))
  (setq y_pos (+ l (/ p_l 2)))
  (setq z_pos (+ (/ h 1.25) p_h))
  (command "_cylinder" (list (+ (car bp) x_pos) (+ (cadr bp) y_pos) (+ (caddr bp) z_pos)) t_r (/ p_h 14)"")
  (command "_union" main (entlast) "")

  (setq btn_w (/ p_w 15))
  (setq btn_l (/ p_l 4))
  (setq y_pos (- (+ l (/ p_l 2)) (/ btn_l 2)))
  (setq x_pos (+ (/ (- w p_w) 2) (/ p_w 2) btn_w))
  (repeat btn_n
    (command "_box" (list (+ (car bp) x_pos) (+ (cadr bp) y_pos) (+ (caddr bp) z_pos)) "_l" btn_w btn_l (/ p_h 28))
    (setq x_pos (+ x_pos (* btn_w 2)))
    (command "_union" main (entlast) "")
    )

  (command "_box" (list (+ (car bp) (/ w 3)) (+ (cadr bp) (/ l 45)) (+ (caddr bp) h)) "_l" (/ w 3) (/ l 5) (/ h -3.4))
  (command "_subtract" main "" (entlast) "")
  (command "_box" bp "_l" h_w (* h_l -1) (/ h 20))
  (setq handler (entlast))

  (command "_-view" "_SWISO")
  (command "_filletedge" (list (car bp) (- (cadr bp) h_l) (+ (caddr bp) (/ h 40))) "_r" h_r "" "")
  (command "_filletedge" (list (+ (car bp) h_w) (- (cadr bp) h_l) (+ (caddr bp) (/ h 40))) "_r" h_r "" "")

  (command "_box" bp "_l" (/ h_w 14)(/ l 11.25) (/ h 60))
  (setq pipe (entlast))
  (command "_box" (list (car bp) (+ (cadr bp) (/ l 11.25) (/ h -60)) (caddr bp)) "_l" (/ h_w 14) (/ h 60) (/ h -2.5))
  (command "_union" pipe (entlast) "")
  (command "_copy" pipe "" bp (list (+ (car bp) (/ h_w 2)) (cadr bp) (caddr bp)))
  (command "_union" pipe (entlast) "")
  (setq x_pos (/ (+ (/ h_w 2) (/ h_w 14)) 2))
  (setq z_pos (/ h 120))
  (command "_move" pipe "" (list (+ (car bp) x_pos) (cadr bp) (+ (caddr bp) z_pos)) (list (+ (car bp) (/ h_w 2)) (cadr bp) (+ (caddr bp) (/ h 40))))
  (command "_union" handler pipe "")
  (command "_move" handler "" (list (+ (car bp) (/ h_w 2)) (cadr bp) (caddr bp))
	   (list (+ (car bp) (/ w 2)) (- (cadr bp) (/ l 45)) (+ (caddr bp) (* h 1.05))))
  
  (command "_union" main handler "")
  (command "_hide")
)
