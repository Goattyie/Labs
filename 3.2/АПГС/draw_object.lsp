(defun c:draw_object()
  (command "osnap" "off")
  (initget 1)
  (setq t1 (getpoint "Базовая точка:"))
  ;(initget (+ 1 2 4))
  ;(setq l (getreal "Длина основания : "))
  ;(initget (+ 1 2 4))
  ;(setq w (getreal "Ширина основания : "))
  ;(initget (+ 1 2 4))
  ;(setq h (getreal "Высота основания : "))
  (setq l 100)
  (setq w 60)
  (setq h 20)
  (command "box" t1 "l" l w h "")
  (setq box1 (entlast))
  ;(initget (+ 1 2 4))
  ;(setq r (getreal "Радиус выемки основания : "))
  (setq r 10)
  (setq c1 (list (car t1) ( + (cadr t1) (/ w 2) ) (caddr t1)))
  (setq c2 (list ( + (car t1) l) ( + (cadr t1) (/ w 2) ) (caddr t1)))
  (command "cylinder" c1 r h "")
  (setq cyl1 (entlast))
  (command "subtract" box1 "" cyl1 "")
  (setq osn (entlast))
  (command "cylinder" c2 r h "")
  (setq cyl2 (entlast))
  (command "subtract" osn "" cyl2 "")
  (setq main (entlast))
  ;(initget (+ 1 2 4))
  ;(setq l2 (getreal "Длина надстройки : "))
  ;(initget (+ 1 2 4))
  ;(setq w2 (getreal "Ширина надстройки : "))
  ;(initget (+ 1 2 4))
  ;(setq h2 (getreal "Высота надстройки : " ))
  (setq l2 40)
  (setq w2 20)
  (setq	h2 60)
  (setq t2 (list( + (car t1) ( / (- l l2) 2))( + (cadr t1) ( / (- w w2) 2)) ( + (caddr t1) h)))
  (command "box" t2 "l" l2 w2 h2 "")
  (setq box2 (entlast))
  ;(initget (+ 1 2 4))
  ;(setq r2 (getreal "Радиус выемки на надстройке : "))
  (setq r2 10)
  (setq c3 (list( + (car t2) (/ l2 2))( cadr t2 )( + (caddr t2) h2)))
  (setq c4 (list( + (car t2) (/ l2 2))( + (cadr t2) w2 )( + (caddr t2) h2)))
  (command "cylinder" c3 r2 "c" c4)
  (setq cyl3 (entlast))
  (command "subtract" box2 "" cyl3 "")
  (command "union" main (entlast) "")
  ;(initget (+ 1 2 4))
  ;(setq l3 (getreal "Длина клина : "))
  ;(initget (+ 1 2 4))
  ;(setq w3 (getreal "Ширина клина : "))
  ;(initget (+ 1 2 4))
  ;(setq h3 (getreal "Высота клина : " ))
  (setq l3 20)
  (setq w3 10)
  (setq h3 60)
  (setq t3 (list ( + (car t2) ( + l2)) ( + (cadr t2) (- (/ w2 2) (/ w3 2))) ( caddr t2)))
  (command "wedge" t3 "l" l3 w3 h3)
  (command "union" main (entlast) "")
  (setq t4 (list( car t2)( + (cadr t2) (- (/ w2 2) (/ w3 2) ))( caddr t2)))
  (setq t5 (list( car t4)(+ (cadr t4) ( / w3 2))( caddr t4)))
  (command "wedge" t4 "l" l3 w3 h3)
  (command "rotate" (entlast) "" t5 180)
  (command "union" main (entlast) "")
  (command "vpoint" (list -1 -1 1))
  (command "hide")
)
